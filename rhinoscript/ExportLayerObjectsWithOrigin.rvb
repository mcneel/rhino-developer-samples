'''''''''''''''''''''''''''''''''''''''''''''''''''''''''''''''''''''''''''''
' ExportLayerObjectsWithOrigin.rvb -- June 2017
' If this code works, it was written by Dale Fugier.
' If not, I don't know who wrote it.
' Works with Rhino5.
'''''''''''''''''''''''''''''''''''''''''''''''''''''''''''''''''''''''''''''

Option Explicit

Sub ExportLayerObjectsWithOrigin
  
	' Declare local variables
	Dim strPath, strFile
	Dim arrLayers, strLayer
	Dim arrSelected
	Dim arrOrigin, strOrigin
	
	' Prompt the user for the origin
	arrOrigin = Rhino.GetPoint("Insertion base point")
	If IsNull(arrOrigin) Then Exit Sub
	strOrigin = Rhino.Pt2Str(arrOrigin, 3, True)
	
	' Disable redrawing
	Call Rhino.EnableRedraw(False)

	' Get the path to and name of the current document.
	' Surround with double-quotes in case path includes spaces.
	strPath = Chr(34) & Rhino.DocumentPath & Rhino.DocumentName & Chr(34)
  
	' Get names of all layers
	arrLayers = Rhino.LayerNames
  
	' Process each layer
	For Each strLayer In arrLayers

		' Unselect all   
		Call Rhino.Command("_-SelNone", 0)
    
		' Select all objects on layer. Surround layer name
		' with double-quotes in case it includes spaces.
		Call Rhino.Command("_-SelLayer " & Chr(34) & strLayer & Chr(34), 0)
   
		' Make sure some objects were selected
		arrSelected = Rhino.SelectedObjects
		If IsArray(arrSelected) Then
      
			' Generate a modified path string
			' that includes the layer name
			strFile = strPath
			strFile = Replace(strFile, ".3dm", "_" & strLayer & ".3dm")
      
			' Export the selected objects
			Call Rhino.Print("Exporting layer: " & strLayer)
			Call Rhino.Command("_-ExportWithOrigin " & strOrigin & strFile, 0)
      
		End If
	Next
  
	' Unselect all
	Call Rhino.Command("_-SelNone", 0)
  
	' Enable redrawing
	Call Rhino.EnableRedraw(True)
    
End Sub
