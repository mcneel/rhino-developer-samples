'''''''''''''''''''''''''''''''''''''''''''''''''''''''''''''''''''''''''''''
' MakeNurbsCircle.rvb -- September 2014
' If this code works, it was written by Dale Fugier.
' If not, I don't know who wrote it.
' Works with Rhino 4.0 and Rhino 5.
'''''''''''''''''''''''''''''''''''''''''''''''''''''''''''''''''''''''''''''
Option Explicit

Sub MakeNurbsCircle

	Dim degree : degree = 2
	Dim cv_count : cv_count = 7
	Dim knot_count: knot_count = cv_count + degree - 1
 
	Dim points() : ReDim points(cv_count-1)
	points(0) = Array(2.500, 0.000, 0.000)
	points(1) = Array(5.000, 0.000, 0.000)
	points(2) = Array(3.750, 2.165, 0.000)
	points(3) = Array(2.500, 4.330, 0.000)
	points(4) = Array(1.250, 2.165, 0.000)
	points(5) = Array(0.000, 0.000, 0.000)
	points(6) = Array(2.500, 0.000, 0.000)
 
	Dim weights() : ReDim weights(cv_count-1)
	weights(0) = 1.0
	weights(1) = 0.5
	weights(2) = 1.0
	weights(3) = 0.5
	weights(4) = 1.0
	weights(5) = 0.5
	weights(6) = 1.0

	Dim knots() : ReDim knots(knot_count-1)
	knots(0) = 0.000
	knots(1) = 0.000
	knots(2) = 0.333
	knots(3) = 0.333
	knots(4) = 0.667
	knots(5) = 0.667
	knots(6) = 1.000
	knots(7) = 1.000

	Call Rhino.AddNurbsCurve(points, knots, degree, weights)

End Sub
